module software {
  yang-version "1.1";
  namespace "urn:fleetmgr:software";
  prefix sw-cfs;

  import stratoweave {
    prefix sw;
  }
  import fleetmgr {
    prefix fleetmgr;
  }

  container software {
    list upgrade-campaign {
      key name;

      sw:transform fleetmgr.cfs.UpgradeCampaign;
      leaf name {
        type string;
      }
      leaf target-release {
        description "Software release the selected devices should be running.";
        type string;
        mandatory true;
      }
      leaf image-url {
        description "Image URL used by devices that pull their own software.";
        type string;
      }
      leaf allow-staging {
        description "Allow the image to be staged before the impacting step.";
        type boolean;
        default "false";
      }
      list device {
        key name;
        description "Devices this campaign upgrades.";
        leaf name {
          sw:link inventory;
          type leafref {
            path "/fleetmgr:fleet/fleetmgr:device/fleetmgr:name";
          }
        }
      }
      leaf admin-state {
        description
          "plan: the campaign is declared and inspectable but does nothing.
           run: the campaign sets the software target on its devices.";
        type enumeration {
          enum plan;
          enum run;
        }
        default plan;
      }

      container state {
        config false;
        leaf total {
          type uint32;
        }
        leaf in-progress {
          type uint32;
        }
        leaf succeeded {
          type uint32;
        }
        leaf failed {
          type uint32;
        }
        list device-status {
          key device;
          leaf device {
            type string;
          }
          leaf status {
            type string;
          }
          leaf running-release {
            type string;
          }
        }
      }
    }
  }
}
