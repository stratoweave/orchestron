module fleetmgr-rfs {
  yang-version "1.1";
  namespace "urn:fleetmgr:rfs";
  prefix fleetmgr-rfs;

  import stratoweave {
    prefix sw;
  }
  import stratoweave-rfs {
    prefix sw-rfs;
  }
  import fleetmgr-types {
    prefix fleetmgr-types;
  }

  augment "/sw-rfs:rfs" {
    container flotilla-status {
      description
        "One subtree-filtered operational feed from this flotilla. Per-device
         software state is normalized here before CFS campaigns aggregate it.";

      sw:rfs-transform fleetmgr.rfs.FlotillaStatus;

      leaf enabled {
        type boolean;
        default "true";
      }

      container state {
        config false;

        list device {
          key name;

          leaf name {
            type string;
          }
          leaf status {
            type string;
          }
          leaf running-release {
            type string;
          }
        }
      }
    }

    list device {
      key name;

      sw:rfs-transform fleetmgr.rfs.Device;

      leaf name {
        type string;
      }

      leaf type {
        type string;
        mandatory true;
      }

      uses fleetmgr-types:device-options;
      uses fleetmgr-types:software-options;
    }
  }
}
