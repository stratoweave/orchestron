module netinfra {
  yang-version "1.1";
  namespace "http://example.com/netinfra";
  prefix "netinfra";
  description "Network Infrastructure";
  revision 2019-01-01 {
    description "test revision";
    reference "ref1";
  }
  import stratoweave {
    prefix sw;
  }
  import ietf-inet-types {
    prefix inet;
  }
  import ietf-yang-types {
    prefix yang;
  }

  container netinfra {
    description "Network infrastructure";
    container global-settings {
      sw:transform mini.cfs.GlobalSettings;
      leaf asn {
        type uint32;
      }
    }
    list ztp-onboarding {
      description "Onboard a CPE via an inline DHCP server on a PE port.";
      key name;

      sw:transform mini.cfs.ZtpOnboarding;

      leaf name {
        description "Name of the CPE device to onboard and create";
        type string;
      }
      leaf serial {
        description "CPE bootstrap identity (SZTP serial); defaults to name";
        type string;
      }
      leaf pe {
        description "PE router that hosts the inline DHCP server";
        type string;
        mandatory true;
      }
      leaf pe-interface {
        description "PE interface facing the CPE (the /31 access link)";
        type string;
        mandatory true;
      }
      leaf link-index {
        description
          "Index of the /31 onboarding link within the onboarding block.
          Deterministically maps to a PE/CPE address pair. A real resource
          manager will assign this; for now it is supplied in config.";
        type uint32;
        mandatory true;
      }
      leaf username {
        description "Day-0 credential the device comes up with (supplied by
          the upstream orchestrator; StratoWeave renders the per-OS config)";
        type string;
        default "admin";
      }
      leaf password {
        type string;
        default "admin";
      }
      leaf onboard-only {
        description "ZTP-as-a-Service: bring the device to day-0 then forget
          it (StratoWeave never manages it; the upstream orchestrator does)";
        type boolean;
        default "false";
      }
    }

    list dhcp-server {
      description
        "A DHCP server that StratoWeave manages as a device. The server
        gives an address to each router that onboards through it, and it
        sends the DHCP options that point the router at StratoWeave.

        StratoWeave owns only the scopes below. The server keeps its own
        plumbing (control channel, lease database, interfaces, loggers).";
      key name;

      sw:transform mini.cfs.DhcpServer;

      leaf name {
        description
          "Name of the DHCP server. StratoWeave creates a device with this
          name.";
        type string;
      }
      leaf type {
        description "Device type of the DHCP server";
        type string;
        default "kea";
      }
      leaf address {
        description "Address of the server's management API";
        type inet:ip-address;
        mandatory true;
      }
      leaf port {
        description "Port of the server's management API";
        type inet:port-number;
        default 8000;
      }
      leaf username {
        description
          "User name for the management API. It defaults to the name of the
          server.";
        type string;
      }
      leaf password {
        description
          "Password for the management API. Leave it unset for a server that
          does not authenticate. StratoWeave then sends no credentials.";
        type string;
      }
      leaf mock {
        description "Do not connect to the server. The tests use this leaf.";
        type boolean;
        default false;
      }

      list scope {
        description
          "One address range that the server serves. A scope is also a ZTP
          bucket: every router that onboards through it gets the same
          bootstrap options.";
        key id;

        leaf id {
          description "Identity of the scope on the server";
          type uint32;
        }
        leaf subnet {
          description "Prefix that the scope serves";
          type inet:ipv4-prefix;
          mandatory true;
        }
        leaf pool-start {
          description "First address in the range that the server assigns";
          type inet:ipv4-address;
          mandatory true;
        }
        leaf pool-end {
          description "Last address in the range that the server assigns";
          type inet:ipv4-address;
          mandatory true;
        }
        leaf gateway {
          description "Default router (DHCP option 3) for the scope";
          type inet:ipv4-address;
        }
        leaf interface {
          description
            "Server interface that serves the scope. Leave it unset to let
            the server select the interface from the prefix.";
          type string;
        }
        leaf valid-lifetime {
          description
            "Lease time in seconds. Always set this value. A server that
            gets no value takes one from its global scope, and then reports
            the value as the scope's own.";
          type uint32;
          default 600;
        }
        leaf sztp {
          description
            "Send the RFC 8572 redirect (DHCP option 143) to every client in
            the scope. Set it to false for a scope that onboards routers
            with classic ZTP only, because option 143 outranks option 67 on
            many platforms.";
          type boolean;
          default true;
        }
      }
    }

    list router {
      key name;

      sw:transform mini.cfs.Router;
      sw:link global {
        sw:path /netinfra/global-settings;
      }

      leaf name {
        type string;
      }
      leaf id {
        type uint32;
        description "router id";
        mandatory true;
      }
      leaf type {
        type string;
        mandatory true;
      }
      leaf mock {
        type boolean;
        default false;
      }
      leaf ztp {
        description "Onboard this router with Zero Touch Provisioning: no
          management address is configured; StratoWeave offers bootstrapping
          data and learns the address from the bootstrap exchange.";
        type boolean;
        default false;
      }
      leaf hostname {
        description "Hostname configured on the router, defaults to the
          router name";
        type string;
      }
      leaf ztp-serial {
        description "Bootstrap identity (serial number) of the router,
          defaults to the router name";
        type string;
      }
      container ztp-dhcp {
        presence
          "Reserve an address for this router on a managed DHCP server";
        description
          "Where the router gets its address and its bootstrap options from.
          StratoWeave writes one reservation into the scope, so it knows the
          router's management address before the router boots. It does not
          have to learn the address from the bootstrap exchange.";
        leaf server {
          description "Name of the dhcp-server that serves this router";
          type string;
          mandatory true;
        }
        leaf scope {
          description "Scope on that server that holds the reservation";
          type uint32;
          mandatory true;
        }
        leaf mac-address {
          description
            "Hardware address that identifies the router to the DHCP server";
          type yang:mac-address;
          mandatory true;
        }
        leaf address {
          description
            "Address to reserve for the router. StratoWeave also uses it as
            the router's management address.";
          type inet:ipv4-address;
          mandatory true;
        }
      }
      container dynstate {
        sw:dynstate;
        leaf current-datetime {
          type string;
        }
      }
      container state {
        config false;
        leaf current-datetime {
          type string;
        }
      }
    }

  }
  // This transform does nothing, just used for testing transform point in P-container
  container p-container {
    presence maybe;
    sw:transform mini.cfs.PContainer;
  }
}
